module fcaps-app {

    yang-version 1;
    namespace "urn:opendaylight:genius:fcaps-app";
    prefix "fcaps";

    import config { prefix config; revision-date 2013-04-05; }
    import opendaylight-md-sal-binding { prefix md-sal-binding; revision-date 2013-10-28; }
    import opendaylight-sal-binding-broker-impl { prefix sal-broker; revision-date 2013-10-28;}
    import opendaylight-entity-ownership-service { prefix eos; }

    description
        "This module contains the base YANG definitions for
        fcaps-manager implementation.";

    revision "2016-05-19" {
        description
            "Initial revision.";
    }

    identity fcaps-app {
            base config:module-type;
            config:java-name-prefix FcapsApp;
    }

    augment "/config:modules/config:module/config:configuration" {
        case fcaps-app {
            when "/config:modules/config:module/config:type = 'fcaps-app'";

            container data-broker {
                uses config:service-ref {
                    refine type {
                        mandatory true;
                        config:required-identity md-sal-binding:binding-async-data-broker;
                    }
                }
            }
            container rpc-registry {
                uses config:service-ref {
                    refine type {
                        mandatory true;
                        config:required-identity md-sal-binding:binding-rpc-registry;
                    }
                }
            }
            container notification-adapter {
                uses config:service-ref {
                    refine type {
                        mandatory true;
                        config:required-identity sal-broker:binding-new-notification-service;
                    }
                }
            }
            container entity-ownership-service {
                uses config:service-ref {
                    refine type {
                        mandatory true;
                            config:required-identity eos:entity-ownership-service;
                    }
                }
            }
        }
    }
}
