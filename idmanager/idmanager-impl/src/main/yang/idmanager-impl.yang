module idmanager-impl {
    yang-version 1;
    namespace "urn:opendaylight:genius:idmanager:impl";
    prefix "idmanager-impl";

    import config { prefix config; revision-date 2013-04-05; }
    import opendaylight-md-sal-binding { prefix md-sal-binding; revision-date 2013-10-28;}

    description
        "Service definition for idmanager project";

    revision "2016-04-06" {
        description
            "Initial revision";
    }

    identity idmanager-impl {
            base config:module-type;
            config:java-name-prefix IdmanagerImpl;
        }

        augment "/config:modules/config:module/config:configuration" {
            case idmanager-impl {
                when "/config:modules/config:module/config:type = 'idmanager-impl'";
                container broker {
                    uses config:service-ref {
                        refine type {
                            mandatory true;
                            config:required-identity md-sal-binding:binding-broker-osgi-registry;
                        }
                    }
                }
                container rpc-registry {
                     uses config:service-ref {
                          refine type {
                             mandatory true;
                             config:required-identity md-sal-binding:binding-rpc-registry;
                          }
                     }
                }

            }
        }
}
