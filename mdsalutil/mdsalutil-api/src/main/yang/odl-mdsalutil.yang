module odl-mdsalutil {
	yang-version 1;
    namespace "urn:opendaylight:genius:mdsalutil";
    prefix "odl-mdsal";

    import config { prefix config; revision-date 2013-04-05; }
 
    description
        "Service definition for MD-SAL Util.";
 
    revision "2016-04-06" {
        description
            "Initial revision";
    }

    identity odl-mdsalutil {
        base "config:service-type";
        config:java-class "org.opendaylight.genius.mdsalutil.interfaces.IMdsalApiManager";
    }
}
