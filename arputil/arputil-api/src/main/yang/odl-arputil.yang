module odl-arputil {
    yang-version 1;
    namespace "urn:opendaylight:genius:arputil";
    prefix "odl-arputil";

    import ietf-interfaces {
        prefix if;
    }

    import ietf-inet-types {
        prefix inet;
    }

    import ietf-yang-types {
        prefix yang;
    }

    revision "2016-04-06" {
        description "Arp Util module";
    }

    grouping interfaces {
        list interface-address {
           key interface;
           leaf interface {
                type leafref {
                    path "/if:interfaces/if:interface/if:name";
                }
           }
           leaf ip-address {
                type inet:ip-address;
           }
           leaf macaddress {
                type yang:phys-address;
            }
        }
    }


    rpc get-mac {
        input {
            leaf ipaddress {
                type inet:ip-address;
            }
            uses interfaces;
        }
        output {
            leaf macaddress {
                type yang:phys-address;
            }
        }
    }

    rpc send-arp-request {
          input {
              leaf ipaddress {
                  type inet:ip-address;
              }
              uses interfaces;
          }
    }

    rpc send-arp-response {
          input {
              leaf dst-ipaddress {
                  type inet:ip-address;
              }
              leaf dst-macaddress {
                  type yang:phys-address;
              }
              leaf interface {
                  type leafref {
                      path "/if:interfaces/if:interface/if:name";
                  }
              }
              leaf src-ipaddress {
                  type inet:ip-address;
              }
              leaf src-macaddress {
                  type yang:phys-address;
              }
          }
    }


    notification mac-changed {
         leaf ipaddress {
             type inet:ip-address;
         }
         leaf macaddress {
             type yang:phys-address;
         }
         leaf interface {
             type leafref {
                path "/if:interfaces/if:interface/if:name";
             }
         }
    }

    notification arp-request-received {
         leaf dst-ipaddress {
             type inet:ip-address;
         }
         leaf src-ipaddress {
             type inet:ip-address;
         }
         leaf src-mac {
             type yang:phys-address;
         }
         leaf of-table-id {
             type uint32;
         }
         leaf interface {
             type leafref {
                path "/if:interfaces/if:interface/if:name";
            }
         }
         leaf metadata {
             type uint64;
         }
         leaf dpn-id {
            type uint64;
         }
    }

    notification arp-response-received {
	  leaf dst-ipaddress {
             type inet:ip-address;
         }
         leaf src-ipaddress {
             type inet:ip-address;
         }
         leaf src-mac {
             type yang:phys-address;
         }
         leaf dst-mac {
             type yang:phys-address;
         }
         leaf of-table-id {
             type uint32;
         }
         leaf interface {
             type leafref {
                path "/if:interfaces/if:interface/if:name";
            }
         }
         leaf metadata {
             type uint64;
         }
         leaf dpn-id {
            type uint64;
         }
    }

}
