module ifm-config {

    namespace "urn:opendaylight:genius:interfacemanager:config";

    prefix ifm-config;

    description "This YANG module defines interfacemanager configuration.";
    revision "2016-04-06";

    /* conf parameters for interfacemanager */
    container ifm-config {
        config true;
        leaf ifm-stats-poll-enabled {
           type boolean;
           default false;
           description "IFM statistics poll flag";
        }
        leaf ifm-stats-def-poll-interval {
           type uint16;
           default 15;
           description "IFM statistics polling interval (in minutes)";
       }
       leaf itm-direct-tunnels {
          description "Enable the ITM to handle tunnels directly by-passing interface manager.";
          type boolean;
          default false;
       }
       leaf itm-of-tunnels {
          description "Enable OF tunnels on ITM Direct Tunnel.";
          type boolean;
          default false;
       }
    }
}
