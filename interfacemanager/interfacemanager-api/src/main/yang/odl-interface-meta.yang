module odl-interface-meta {
    namespace "urn:opendaylight:genius:interfacemanager:meta";
    prefix "odlifmeta";

    import ietf-interfaces {
        prefix if;
    }

    import ovsdb {
        prefix southbound; revision-date "2015-01-05";
    }

    revision "2016-04-06" {
        description "ODL rendering specific Interface Manager Meta Module";
    }

    container bridge-interface-info {
        description "Contains the list of dpns along with the tunnel interfaces configured on them.";

        list bridge-entry {
            key dpid;
            leaf dpid {
                type uint64;
            }

            leaf bridge-reference {
                type southbound:ovsdb-bridge-ref;
                description "This is the reference to an ovs bridge";
            }
            list bridge-interface-entry {
                key interface-name;
                leaf interface-name {
                    type string;
                }
            }
        }
    }

    container bridge-ref-info {
        config false;
        description "The container that maps dpid with ovs bridge ref in the operational DS.";

        list bridge-ref-entry {
            key dpid;
            leaf dpid {
                type uint64;
            }

            leaf bridge-reference {
                type southbound:ovsdb-bridge-ref;
                description "This is the reference to an ovs bridge";
            }
        }
    }

    container interface-child-info {
        description "The container of all Child-Interfaces for a given interface.";
        list interface-parent-entry {
            key parent-interface;
            leaf parent-interface {
                type string;
            }

            list interface-child-entry {
                key child-interface;
                leaf child-interface {
                    type string;
                }
            }
        }
    }

   container if-indexes-interface-map {
           config false;
           list if-index-interface {
               key if-index;
               leaf if-index {
                   type int32;
               }
               leaf interface-name {
                   type string;
               }
           }
   }

   container interface-monitor-id-map {
       config false;
       list interface-monitor-id {
           key interface-name;
           leaf interface-name {
               type string;
           }
           leaf-list monitor-id {
               type uint32;
           }
       }
   }

   container monitor-id-interface-map {
       config false;
       list monitor-id-interface {
           key monitor-id;
           leaf monitor-id {
               type uint32;
           }
           leaf interface-name {
               type string;
           }
       }
   }

   container tunnel-instance-interface-map {
          config false;
          list tunnel-instance-interface {
              key tunnel-instance-identifier;
              leaf tunnel-instance-identifier {
                  type string;
              }
              leaf interface-name {
                  type string;
              }
          }
   }

   container dpn-to-interface-list {
        config false;
        description "Contains the list of interfaces on the given dpn";

        list dpn-to-interface {
            key dpid;
            leaf dpid {
                type uint64;
            }
            list interface-name-entry {
                key interface-name;
                leaf interface-name {
                    type string;
                }
                leaf interface-type {
                    type identityref {
                        base if:interface-type;
                    }
                }
            }
        }
   }
}
