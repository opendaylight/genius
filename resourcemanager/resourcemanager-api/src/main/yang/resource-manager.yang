module resource-manager {
    namespace "urn:opendaylight:genius:resourcemanager";
    prefix resourcemgr;

    import id-manager {
        prefix idmgr;
    }

    revision "2016-06-22" {
        description "YANG model exposes RPCs that can be used by the applications for allocating a block of IDs for tables, groups, meters, etc. This yang-model enables ODL Resource Sharing Framework";
    }


    identity resource-type-base {
        description "Base identity for all resource-types";
    }

    identity resource-type-table-ids {
        description "Resource type for tables";
        base resource-type-base;
    }

    identity resource-type-group-ids {
        description "Resource type for groups";
        base resource-type-base;
    }

    identity resource-type-meter-ids {
        description "Resource type for meters";
        base resource-type-base;
    }

    rpc releaseResource {
        input {
             leaf resource-type {
                type identityref{
                    base resource-type-base;
                }
             }
             leaf id-key {
                type string;
             }
        }
    }

    rpc allocateResource {
        input {
             leaf resource-type {
                type identityref{
                    base resource-type-base;
                }
             }
             leaf id-key {
                type string;
             }
             leaf size {
                type uint32;
             }
        }
        output {
             leaf-list id-values{
                type uint32;
                ordered-by user;
             }
        }
    }

    rpc getAvailableResources{
        input {
             leaf resource-type {
                type identityref{
                    base resource-type-base;
                }
             }
        }
        output{
             leaf total-available-id-count {
                type uint32;
             }
        }
    }

    rpc getResourcePool{
        input{
             leaf resource-type {
                type identityref{
                    base resource-type-base;
                }
             }
        }
        output{
             list available-ids{
                uses available-resource-ids;
             }
             uses released-resource-ids;
        }
    }

    grouping available-resource-ids {
        leaf start {
             type uint32;
        }
        leaf end {
             type uint32;
        }
    }

    grouping released-resource-ids {
        list delayed-resource-entries {
            uses idmgr:delayed-id-entry;
        }
    }
}
