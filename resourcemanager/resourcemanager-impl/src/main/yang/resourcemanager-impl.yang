module resourcemanager-impl {
    yang-version 1;
    namespace "urn:opendaylight:genius:resourcemanager:impl";
    prefix "resourcemanager-impl";

    import config { prefix config; revision-date 2013-04-05; }
    import opendaylight-md-sal-binding { prefix md-sal-binding; revision-date 2013-10-28;}
    import odl-mdsalutil { prefix odl-mdsal; revision-date 2016-04-06;}

    description
        "Service definition for resourcemanager project";

    revision "2016-04-06" {
        description
            "Initial revision";
    }

    identity resourcemanager-impl {
            base config:module-type;
            config:java-name-prefix ResourceManagerImpl;
        }

        augment "/config:modules/config:module/config:configuration" {
            case resourcemanager-impl {
                when "/config:modules/config:module/config:type = 'resourcemanager-impl'";
                container broker {
                    uses config:service-ref {
                        refine type {
                            mandatory true;
                            config:required-identity md-sal-binding:binding-broker-osgi-registry;
                        }
                    }
                }
                container rpc-registry {
                     uses config:service-ref {
                          refine type {
                             mandatory true;
                             config:required-identity md-sal-binding:binding-rpc-registry;
                          }
                     }
                }
                container mdsalutil {
                      uses config:service-ref {
                            refine type {
                               mandatory true;
                               config:required-identity odl-mdsal:odl-mdsalutil;
                            }
                      }
                }
            }
        }
}
