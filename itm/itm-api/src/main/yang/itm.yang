module itm {
    namespace "urn:opendaylight:genius:itm";

    prefix "itm";

    import ietf-inet-types {
        prefix inet;
        revision-date "2013-07-15";
    }

    import odl-interface {
        prefix odlif;
    }


    revision "2016-04-06" {
        description "ODL Internal Transport Module";
    }

    /* Configuration data */

    container transport-zones {
          list transport-zone {
            ordered-by user;
            key zone-name;
            leaf zone-name {
                type string;
                mandatory true;
            }
            leaf tunnel-type {
                type identityref {
                    base odlif:tunnel-type-base;
                }
                mandatory true;
            }
            list vteps {
                key "dpn-id";
                leaf dpn-id {
                    type uint64;
                }
                leaf ip-address {
                    type inet:ip-address;
                }
                leaf option-of-tunnel {
                    description "Use flow based tunnels for remote-ip";
                    type boolean;
                    default false;
                }
                leaf option-tunnel-tos {
                    description "Value of ToS bits to be set on the encapsulating
                        packet.  The value of 'inherit' will copy the DSCP value
                        from inner IPv4 or IPv6 packets.  When ToS is given as
                        a numberic value, the least significant two bits will
                        be ignored.";
                    type string {
                        length "1..8";
                    }
                }
            }
             list device-vteps {
                 key "node-id ip-address";

                 leaf topology-id {
                     type string;
                 }
                 leaf node-id {
                     type string;
                 }
                 leaf ip-address {
                     type inet:ip-address;
                 }
             }
		 }
    }

    container not-hosted-transport-zones {
        config false;
        list tepsInNotHostedTransportZone {
            key zone-name;
            leaf zone-name {
                type string;
            }
            list unknown-vteps{
                key "dpn-id";
                leaf dpn-id {
                    type uint64;
                }
                leaf ip-address {
                    type inet:ip-address;
                }
                leaf of-tunnel {
                    description "Use flow based tunnels for remote-ip";
                    type boolean;
                    default false;
                }
                leaf option-tunnel-tos {
                    description "Value of ToS bits to be set on the encapsulating
                           packet.  The value of 'inherit' will copy the DSCP value
                           from inner IPv4 or IPv6 packets.  When ToS is given as
                           a numberic value, the least significant two bits will
                           be ignored.";
                    type string {
                        length "1..8";
                    }
                }
            }
        }
    }

    container dc-gateway-ip-list{
        status deprecated;
        list dc-gateway-ip{
            key "ip-address";
            leaf ip-address{
                type inet:ip-address;
            }
            leaf tunnnel-type{
                type identityref {
                    base odlif:tunnel-type-base;
                }
            }
        }
    }
}
