module itm-config {

    namespace "urn:opendaylight:genius:itm:config";

    prefix itm-config;

    import odl-interface {
            prefix odlif;
    }

    description "This YANG module defines automatic tunnel configuration.";
    revision "2016-04-06";

    /* Tunnel Monitoring Knob */

    container tunnel-monitor-params {
      leaf enabled {
         type boolean;
         default false;
      }

      leaf monitor-protocol {
         type identityref {
             base odlif:tunnel-monitoring-type-base;
         }
         default odlif:tunnel-monitoring-type-bfd;
      }
    }
    container tunnel-monitor-interval {
      leaf interval {
         type uint16 {
             range "1000..30000";
         }
      }
    }

    /* conf parameters for default-transport-zone */
    container itm-config {
       config true;
       leaf def-tz-enabled {
          type boolean;
          default false;
       }
       leaf def-tz-tunnel-type {
          type string;
          default "vxlan";
       }
       list tunnel-aggregation {
            key "tunnel-type";
            leaf tunnel-type {
                type string;
            }

            leaf enabled {
                type boolean;
                default false;
            }
       }
       leaf default-tunnel-tos {
           description "Default value of ToS bits to be set on the encapsulating
               packet. The value of 'inherit' will copy the DSCP value
               from inner IPv4 or IPv6 packets.  When ToS is given as
               a numberic value, the least significant two bits will
               be ignored.";

            type string {
                length "1..8";
            }
            default 0;
       }
       leaf gpe-extension-enabled {
            description "Enable the GPE extension for VXLAN tunnel interfaces
                configured through ITM.";
            type boolean;
            default false;
       }
       leaf use-of-tunnels {
          description "Enable OF tunnels on ITM Direct Tunnel.";
          type boolean;
          default false;
       }
       leaf vlan-id {
           type uint16{
             range "0..4094";
           }
       }
       leaf portname {
           type string;
       }
       leaf batch-interval {
            type uint16;
       }
       leaf batch-size {
            type uint16;
       }
    }
}
