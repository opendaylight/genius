module odl-itm-meta {
    namespace "urn:opendaylight:genius:itm:meta";
    prefix "odlitmmeta";

    import ietf-interfaces {
        prefix if;
    }

    import ovsdb {
        prefix southbound; revision-date "2015-01-05";
    }

    revision "2017-12-10" {
        description "ODL rendering specific ITM Meta Module";
    }

    container bridge-tunnel-info {
        description "Contains the list of dpns along with the tunnel interfaces configured on them.";

        list ovs-bridge-entry {
            key dpid;
            leaf dpid {
                type uint64;
            }
            leaf ovs-bridge-reference {
                type southbound:ovsdb-bridge-ref;
                description "This is the reference to an ovs bridge";
            }
            list ovs-bridge-tunnel-entry {
                key tunnel-name;
                leaf tunnel-name {
                    type string;
                }
            }
        }
    }

    container ovs-bridge-ref-info {
        config false;
        description "The container that maps dpid with ovs bridge ref in the operational DS.";

        list ovs-bridge-ref-entry {
            key dpid;
            leaf dpid {
                type uint64;
            }
            leaf ovs-bridge-reference {
                type southbound:ovsdb-bridge-ref;
                description "This is the reference to an ovs bridge";
            }
        }
    }

    container if-indexes-tunnel-map {
           config false;
           list if-index-tunnel {
               key if-index;
               leaf if-index {
                   type int32;
               }
               leaf interface-name {
                   type string;
               }
           }
   }

   container dpn-to-interface-list {
        config false;
        description "Contains the list of interfaces on the given dpn";

        list dpn-to-interface {
            key dpid;
            leaf dpid {
                type uint64;
            }
            list interface-name-entry {
                key interface-name;
                leaf interface-name {
                    type string;
                }
                leaf interface-type {
                    type identityref {
                        base if:interface-type;
                    }
                }
            }
        }
   }

   container interface-child-info {
      description "The container of all child-interfaces for an interface.";

      list interface-parent-entry {
          key parent-interface;
          leaf parent-interface {
              type string;
          }

          list interface-child-entry {
              key child-interface;
              leaf child-interface {
                  type string;
              }
          }
      }
   }
}
